Attribute VB_Name = "Main"
Public Sub ShowForm()
    Dim UserForm As New frmMain
    Load UserForm
    UserForm.show
    Unload UserForm
End Sub

Attribute VB_Name = "frmMain"
Attribute VB_Base = "0{9748F4E2-EBE9-40F4-BA45-497265BC7AEE}{9D289678-AAC5-4E8B-A9BC-A134AD736B15}"
Attribute VB_GlobalNameSpace = False
Attribute VB_Creatable = False
Attribute VB_PredeclaredId = True
Attribute VB_Exposed = False
Attribute VB_TemplateDerived = False
Attribute VB_Customizable = False
'''''''''''''''''''''''''''''''''''''''''''''''''''''''''''''''''''''''''''''''''''''''
'''''''''''''''''''''''''''''''''''''''''''''''''''''''''''''''''''''''''''''''''''''''
''' Perfil de Esgoto - Versão 003                                                   '''
'''                                                                                 '''
''' Por: Pedro Henrique Teles de Carvalho @ SANEAGO                                 '''
''' Em:  28/03/2019                                                                 '''
'''                                                                                 '''
''' Melhorias:                                                                      '''
'''     V.002 - salvar e carregar dados a partir de arquivos txt/csv                '''
'''     V.003 - validação de dados, editar e excluir de linhas                      '''
'''                                                                                 '''
'''''''''''''''''''''''''''''''''''''''''''''''''''''''''''''''''''''''''''''''''''''''
'''''''''''''''''''''''''''''''''''''''''''''''''''''''''''''''''''''''''''''''''''''''

''''' Constantes e variaveis ''''
' Tabela de trechos '
Const NCOLS_EDIT As Integer = 9     ' numero de colunas da tabela editavel
Const NCOLS_CALC As Integer = 4     ' numero de colunas da tabela calculada
Dim nLinhas As Integer              ' numero de linhas preenchidas
' Desenho dos PVs
Dim diametroPV As Double, raioPV As Double, escXYelPV As Double
' Variáveis de texto
Dim htextos As Double, offsetTextos As Double
Dim precisaoCotas As Integer
' Eixos X e Y
Dim offsetEixos As Double, tick As Double
Dim dxEixoY As Double, dyEixoY As Double
Dim gapY As Integer, precisaoEixos As Integer
Dim escY As Double
' Tabela Inferior
Dim dxRotulosInf As Double, hLinhaInfo As Double
Dim hTabInfo As Double, hTextInfo As Double
Dim nLinhasInfo As Integer
Dim rotulosInfo As Variant      ' Rótulos da tabela inferior
' Leaders
Dim projLd As Integer, dxLd As Integer
' Cota máxima e mínima
Dim cotaMax As Double, cotaMin As Double
' Calculo
Dim errLamina As Double, maxTentativas As Integer
Dim pesoLiq As Double, nManning As Double
Dim alertas As String

' Configura o formulário para iniciar
Private Sub UserForm_Initialize()
    nLinhas = 0                 ' numero inicial de linhas na tabela do UserForm
    errLamina = 10 ^ (-20)
    pesoLiq = 10 ^ 4
    maxTentativas = 1000
    nManning = 0.013
    dxMax = 25
    
    Call MsgBox("ATENÇÃO - Nas entradas de dados, utilize a VÍRGULA como separador de decimais. P.ex.: 1234,56", _
        VbMsgBoxStyle.vbOKOnly, _
        "Geração de Perfis Longitudinais - Esgoto")
        
    Teste
End Sub

' Ao clicar no botão "Abrir", solicita ao usuário informar um arquivo cujos dados previamente salvos serão carregados na aplicação
Private Sub cmdAbrir_Click()
    FileDialogBox.CancelError = True
    On Error GoTo ErrorHandler
    FileDialogBox.FileName = ""
        
    Dim iNR As Integer
    Dim arquivo As String
    
    ' Solicita ao usuário que selecione ou entre o nome de um arquivo para abrir
    FileDialogBox.ShowOpen
    
    ' Abre o arquivo indicado
    arquivo = FileDialogBox.FileName
    iNR = FreeFile
    Open arquivo For Input As #iNR
    
    ' Declara as variáveis
    Dim currentLine As String
    Dim vars() As String
    Dim trecho As Integer
    Dim ctTopo1 As Double, ctTopo2 As Double, dist As Double
    Dim prof1 As Double, prof2 As Double
    Dim material As String
    Dim dn As Integer
    Dim vazao As Double
    
    ' Inicia o loop de leitura das linhas
    While Not EOF(iNR)
        ' Lê a linha corrente e busca as variáveis
        Line Input #iNR, currentLine
        vars() = Split(currentLine, ";", NCOLS_EDIT)
        
        ' Verifica se a linha possui o número correto de parâmetros
        If GetLength(vars()) = NCOLS_EDIT Then
            ' Tenta carregar as variáveis a partir da linha de texto
            trecho = valueFromString(vars(0))
            ctTopo1 = valueFromString(vars(1))
            ctTopo2 = valueFromString(vars(2))
            prof1 = valueFromString(vars(3))
            prof2 = valueFromString(vars(4))
            dist = valueFromString(vars(5))
            material = vars(6)
            dn = valueFromString(vars(7))
            vazao = valueFromString(vars(8))
            
            Call AddLinha(trecho, ctTopo1, ctTopo2, prof1, prof2, dist, material, dn, vazao)
            
        Else
            MsgBox "Leitura do arquivo concluída."
            Exit Sub
        End If
    Wend
    
    ' Fecha o arquivo
    MsgBox "Leitura do arquivo concluída."
    Close #iNR
    iNR = FreeFile
    
    Exit Sub
    
ErrorHandler:
    MsgBox ("Ação cancelada.")
    Exit Sub
End Sub

' Ao clicar no botão "Salvar", salva o arquivo com extensão txt
Private Sub cmdSalvar_Click()
    FileDialogBox.CancelError = True
    
    On Error GoTo ErrorHandler
    FileDialogBox.FileName = ""
    
    Dim iNR As Integer
    Dim arquivo As String
    
    ' Solicita ao usuário que selecione ou entre o nome de um arquivo para salvar
    FileDialogBox.ShowSave
            
    ' Caso seja um arquivo existente, pergunte se deseja sobrescrever
    arquivo = FileDialogBox.FileName
    If FileExists(arquivo) Then
        result = MsgBox("O arquivo já existe. Deseja sobrescrever?", vbYesNo, "Alerta")
        
        ' Caso o usuário deseje sobrescrever, deleta o arquivo e continua
        If result = vbYes Then
            Kill (arquivo)
        ' Caso o usuário decida não sobrescrever, aborta o comando
        Else
            GoTo ErrorHandler
        End If
    End If
      
    ' Escreve as linhas do script no arquivo
    iNR = FreeFile
    Open arquivo For Append As #iNR

    Dim i As Integer
    i = 0
    Dim trecho As Integer
    Dim ctTopo1 As Double, ctTopo2 As Double, dist As Double
    Dim prof1 As Double, prof2 As Double
    Dim material As String
    Dim dn As Integer
    Dim vazao As Double
    While i < nLinhas
        trecho = valueFromString(Me.ListBoxEdit.Column(0, i))
        ctTopo1 = valueFromString(Me.ListBoxEdit.Column(1, i))
        prof1 = valueFromString(Me.ListBoxEdit.Column(2, i))
        ctTopo2 = valueFromString(Me.ListBoxEdit.Column(3, i))
        prof2 = valueFromString(Me.ListBoxEdit.Column(4, i))
        dist = valueFromString(Me.ListBoxEdit.List(i, 5))
        material = Me.ListBoxEdit.List(i, 6)
        dn = valueFromString(Me.ListBoxEdit.List(i, 7))
        vazao = valueFromString(Me.ListBoxEdit.List(i, 8))
        
        savedString = NumToStr(trecho, 0) & ";" & DblToStr(ctTopo1) & ";" & DblToStr(ctTopo2) & ";" & DblToStr(prof1) & ";" & DblToStr(prof2) _
                        & ";" & DblToStr(dist) & ";" & material & ";" & NumToStr(dn, 0) & ";" & DblToStr(vazao)
        Print #iNR, savedString
        i = i + 1
    Wend
    ' Fecha o arquivo
    Close #iNR
    iNR = FreeFile
    Exit Sub
    
ErrorHandler:
    MsgBox ("Ação cancelada.")
    Exit Sub

End Sub

' Ao clicar no botão "Gerar Perfil", desenha o perfil longitudinal da rede
Private Sub cmdGerarPerfil_Click()
''' Inicializa as variáveis
    alertas = ""
    ' Desenho do PV
    diametroPV = 3
    raioPV = diametroPV / 2
    escXYelPV = 0.1
    ' Variáveis de texto
    htextos = frmMain.TxBxHTextos.Value
    offsetTextos = 1#
    precisaoCotas = 2
    ' Eixos X e Y
    offsetEixos = 10    ' distância mínima do eixo Y até o desenho
    tick = 3            ' tamanho do tick (pequena linha p/ identiciçao) nos eixos horizontal e vertical
    dxEixoY = 5         ' dimensoes dx e dy dos rotulos do eixo Y
    dyEixoY = 1.5
    gapY = Me.TxBxGapY.Value   ' intervalo das cotas entre os ticks
    precisaoEixos = 0   ' Precisão dos valores dos eixos
    escY = CDbl(Me.TxBxEscY.Value)
    ' Tabela Inferior
    hTextInfo = Me.TxBxHTextos.Value        ' Altura dos textos da tabela de informações
    dxRotulosInf = 15                       ' Tamanho da coluna inicial com os rotulos na tabela de informações
    rotulosInfo = Array("Extensão", "Material / DN", "Declividade", "Vazão", "Lâmina (y/D)") ' Rotulos
    nLinhasInfo = GetLength(rotulosInfo)    ' Nº de linhas da tabela de informações
    hLinhaInfo = 5                          ' Altura de cada linha da tabela de informações
    hTabInfo = hLinhaInfo * nLinhasInfo     ' Altura total da tabela de informações
    ' Leaders
    projLd = 5      ' Projeção horizontal=vertical da linha de chamada do Leader X
    dxLd = 8        ' Dimensão da linha horizontal do Leader
    
    ' Arrays e variaveis dos elementos do perfil
    Dim xAcum As Double
    xAcum = offsetEixos
    ReDim pLineTopo(0 To 2 * 2 * nLinhas - 1) As Double
    ReDim pLineFundo(0 To 2 * (2 * nLinhas + 1) - 1) As Double
    cotaMax = cotaMaxima()
    cotaMin = cotaMinima()
    
    ' Desenha cada um dos trechos
    Dim i As Integer
    i = 0
    Dim ctTopo1 As Double, ctTopo2 As Double, dist As Double
    Dim prof1 As Double, prof2 As Double, profChega As Double, yChega As Double
    Dim x11 As Double, x12 As Double, yTopo1 As Double, yFundo1 As Double
    Dim x21 As Double, x22 As Double, yTopo2 As Double, yFundo2 As Double
    Dim material As String
    Dim dn As Double
    Dim vazao As Double
    Dim decliv As Double
    Dim lamina As Double
    Dim infos As Variant
    
    profChega = 0
    yChega = 0
    While i < nLinhas
        ' Calcula as variaveis
        If (i > 0) Then
            profChega = prof2
            yChega = yFundo2
        End If
        
        ' Cota de topo a montante
        ctTopo1 = valueFromString(Me.ListBoxEdit.Column(1, i))
        If ((i > 0) And (ctTopo1 <> ctTopo2)) Then
            alertas = alertas & "Inconsistência na cota de topo do PV " & NumToStr(i + 1, 0) & vbCrLf
        End If
        
        ' Profundidade a montante
        prof1 = valueFromString(Me.ListBoxEdit.Column(2, i))
        If (((i > 0) And (prof1 < prof2)) Or (prof1 <= 0)) Then
            alertas = alertas & "Inconsistência na profundidade do PV " & NumToStr(i + 1, 0) & vbCrLf
        End If
        
        ' Coordenadas gráficas do desenho a montante
        yTopo1 = coordY(ctTopo1)
        yFundo1 = coordY(ctTopo1 - prof1)
        x11 = xAcum - raioPV
        x12 = xAcum + raioPV
        
        ' Cota de topo a jusante
        ctTopo2 = valueFromString(Me.ListBoxEdit.Column(3, i))
        
        ' Profundidade a justante
        prof2 = valueFromString(Me.ListBoxEdit.Column(4, i))
        If (prof2 <= 0) Then
            alertas = alertas & "Inconsistência na profundidade do PV " & NumToStr(i + 2, 0) & vbCrLf
        End If
        
        ' Distância
        dist = valueFromString(Me.ListBoxEdit.List(i, 5))
        
        ' Material
        material = Me.ListBoxEdit.List(i, 6)
        
        ' Diâmetro
        dn = valueFromString(Me.ListBoxEdit.List(i, 7))
        
        ' Vazão
        vazao = valueFromString(Me.ListBoxEdit.List(i, 8))
        If (vazao < 0) Then
            vazao = 0
        End If
        
        ' Declividades
        decliv = valueFromString(Me.ListBoxCalc.List(i, 0))
        If (decliv < 0) Then
            alertas = alertas & "Declividade negativa no trecho " & NumToStr(i + 1, 0) & vbCrLf
        ElseIf (decliv < 0.05) Then
            alertas = alertas & "Declividade negativa no trecho " & NumToStr(i + 1, 0) & vbCrLf
        End If
        
        ' Lâmina
        lamina = valueFromString(Me.ListBoxCalc.List(i, 1))
        If (lamina > 0.75) Then
            alertas = alertas & "Lâmina (y/D) maior que 75% no trecho " & NumToStr(i + 1, 0) & vbCrLf
        ElseIf (lamina > 0.5) Then
            alertas = alertas & "Lâmina (y/D) maior que 50% no trecho " & NumToStr(i + 1, 0) & ". Verificar velocidade máxima." & vbCrLf
        End If
        
        ' Define informações do trecho
        infos = Array(NumToStr(dist, 1) & " m", _
                      material & " / " & NumToStr(dn, 0) & " mm", _
                      NumToStr(decliv, 2) & "%", _
                      NumToStr(vazao, 2) & " L/s", _
                      NumToStr(lamina, 1) & "%")
       
        ' Popula as polylines de topo e fundo
        pLineTopo(4 * i) = x12
        pLineTopo(4 * i + 1) = yTopo1
        pLineFundo(4 * i) = x12
        pLineFundo(4 * i + 1) = yFundo1
        
        ' Desenha PV inicial de cada trecho c/ infos e leader de topo
        obj = desenhaPV(xAcum, yTopo1, yFundo1, ctTopo1, prof1)
        
        ' Desenha leader de fundo (se for o caso)
        If ((i > 0) And (prof1 > profChega)) Then
            Call desenhaLeader(x11, yChega, -1, -1, "PROF", DblToStr(profChega))
        End If
        
        ' Popula Polylines de topo e de fundo
        xAcum = xAcum + dist
        x21 = xAcum - raioPV
        x22 = xAcum + raioPV
        yTopo2 = coordY(ctTopo2)
        yFundo2 = coordY(ctTopo2 - prof2)
        
        ' Popula Polylines de topo e de fundo
        pLineTopo(4 * i + 2) = x21
        pLineTopo(4 * i + 3) = yTopo2
        pLineFundo(4 * i + 2) = x21
        pLineFundo(4 * i + 3) = yFundo2
        i = i + 1
        
        ' Insere as informações do trecho na tabela Inferior
        Call insereTextosTabInf(xAcum - dist / 2, infos)
    Wend
        
    ' Desenha PV final c/ informações e leaders de topo e fundo
    obj = desenhaPV(xAcum, yTopo2, yFundo2, ctTopo2, prof2)
    
    ' Popula Polylines de topo e de fundo
    pLineFundo(4 * i) = x22
    pLineFundo(4 * i + 1) = yFundo2
    
    ' Desenha Polylines de topo e de fundo
    Set obj = ThisDrawing.ModelSpace.AddLightWeightPolyline(pLineTopo)
    Set obj = ThisDrawing.ModelSpace.AddLightWeightPolyline(pLineFundo)
    
    ' Desenha eixos
    ' Variáveis
    Dim cotaRotY As Double, coordEixoY As Double
    cotaRotY = Fix((cotaMax / gapY) + 1) * gapY
    coordEixoY = coordY(cotaRotY)
    ' Eixo Y
    Set obj = ThisDrawing.ModelSpace.AddLine( _
        ponto(0#, coordEixoY), _
        ponto(0#, 0#))
    ' Eixo X
    Set obj = ThisDrawing.ModelSpace.AddLine( _
        ponto(xAcum, 0#), _
        ponto(-dxRotulosInf, 0#))
    ' Rotulos e Ticks do Eixo Y
    Dim textObj As AcadText
    Dim pt As Variant
    While (coordEixoY >= 0)
        ' Ponto de inserção
        pt = ponto(-offsetTextos, coordEixoY + offsetTextos)
        ' Insere e alinha o texto
        Set textObj = ThisDrawing.ModelSpace.AddText(CStr(cotaRotY), pt, dyEixoY)
        textObj.Alignment = acAlignmentBottomRight
        textObj.TextAlignmentPoint = pt
        ' Insere o tick
        If (coordEixoY > 0) Then
            Set obj = ThisDrawing.ModelSpace.AddLine(ponto(0#, coordEixoY), ponto(-tick, coordEixoY))
        End If
        ' Incrementa ou decresce as variáveis
        ThisDrawing.Regen acActiveViewport
        cotaRotY = cotaRotY - gapY
        coordEixoY = coordY(cotaRotY)
    Wend
    
    ' Desenha tabela inferior
    ' Insere o Cabeçalho
    Call insereTextosTabInf((offsetEixos - dxRotulosInf) / 2, rotulosInfo)
    ' Insere Linhas Horizontais
    coordEixoY = -hLinhaInfo
    While (coordEixoY >= -hTabInfo)
        Set obj = ThisDrawing.ModelSpace.AddLine(ponto(-dxRotulosInf, coordEixoY), ponto(xAcum, coordEixoY))
        coordEixoY = coordEixoY - hLinhaInfo
    Wend
    ' Insere a linha vertical inicial
    Set obj = ThisDrawing.ModelSpace.AddLine(ponto(-dxRotulosInf, 0#), ponto(-dxRotulosInf, -hTabInfo))
    
    ' Confirma perfil gerado
    Set textObj = Nothing
    Set obj = Nothing
    ThisDrawing.Application.ZoomExtents
    MsgBox "Perfil gerado."
    
    ' Mostra alertas
    If Not (alertas = vbNullString) Then
        MsgBox alertas
    End If
    
End Sub

' Retorna o valor numerico da lista (ie. lida com os separadores de unidades, etc.)
Public Function valueFromString(x As String)
    Dim xReplaced As String
    xReplaced = Replace(x, ",", ".")
    If (StrComp(x, xReplaced, vbTextCompare) = 0) Then
        valueFromString = Int(xReplaced)
    Else
        valueFromString = CDbl(Val(xReplaced))
    End If
End Function

' Adiciona linha à tabela de trechos
Public Sub AddLinha(trecho As Integer, ctMont As Double, ctJus As Double, _
            profMont As Double, profJus As Double, dist As Double, _
            mat As String, dn As Integer, vazao As Double)
    
    alertas = ""
    
    ' Validações
    ' Trecho
    If (trecho <= 0) Then
        alertas = alertas & "Número do trecho incoerente."
    ElseIf (trecho > nLinhas + 1) Then
        alertas = alertas & "Número do trecho incoerente, favor corrigir." & vbCrLf
    End If
    ' Cota Montante
    Dim ctTrechoAnt As Double
    If (trecho > 1) Then
        ctTrechoAnt = valueFromString(Me.ListBoxEdit.List(trecho - 2, 3))
        If (ctMont <> ctTrechoAnt) Then
            alertas = alertas & "Inconsistência na cota de topo do PV " & NumToStr(i + 1, 0) & vbCrLf
        End If
    End If
    ' Cota a Jusante
    ' TODO
    '
    ' Profundidade a Montante
    Dim profTrechoAnt As Double
    If (trecho > 1) Then
        profTrechoAnt = valueFromString(Me.ListBoxEdit.List(trecho - 2, 4))
        If ((profMont < profTrechoAnt) Or (profMont <= 0)) Then
            alertas = alertas & "Inconsistência na profundidade do PV " & NumToStr(i + 1, 0) & vbCrLf
        End If
    End If
    ' Profundidade a Jusante
    If (profJus <= 0) Then
        alertas = alertas & "Inconsistência na profundidade do PV " & NumToStr(i + 2, 0) & vbCrLf
    End If
    ' Extensão
    ' TODO
    '
    ' Vazão
    ' TODO
    '
   
    ' Verifica se já existe o nº do trecho indicado
    If (trecho > nLinhas) Then
        ' Se o trecho indicado não houver sido criado ainda, incrementa o numero de linhas
        Me.ListBoxEdit.AddItem (nLinhas)
        Me.ListBoxCalc.AddItem (nLinhas)
        nLinhas = nLinhas + 1
    End If
    
    ' Adiciona trecho no Listbox
    Me.ListBoxEdit.List(trecho - 1, 0) = trecho
    Me.ListBoxEdit.List(trecho - 1, 1) = DblToStr(ctMont)
    Me.ListBoxEdit.List(trecho - 1, 2) = DblToStr(profMont)
    Me.ListBoxEdit.List(trecho - 1, 3) = DblToStr(ctJus)
    Me.ListBoxEdit.List(trecho - 1, 4) = DblToStr(profJus)
    Me.ListBoxEdit.List(trecho - 1, 5) = DblToStr(dist)
    Me.ListBoxEdit.List(trecho - 1, 6) = mat
    Me.ListBoxEdit.List(trecho - 1, 7) = dn
    Me.ListBoxEdit.List(trecho - 1, 8) = DblToStr(vazao)
    
    ' Calcula a declividade
    Dim decliv As Double
    decliv = ((ctMont - profMont) - (ctJus - profJus)) * 100 / dist
    If (decliv < 0) Then        ' Gera alertas
        alertas = alertas & "Declividade negativa no trecho " & NumToStr(i + 1, 0) & vbCrLf
    ElseIf (decliv < 0.05) Then
        alertas = alertas & "Declividade negativa no trecho " & NumToStr(i + 1, 0) & vbCrLf
    End If
    Me.ListBoxCalc.List(trecho - 1, 0) = DblToStr(decliv)
    
    ' Calcula a lâmina
    Dim yD As Double
    yD = lamina(vazao, dn, decliv / 100, nManning)
    If (yD >= 0.75) Then        ' Gera alertas
        alertas = alertas & "Lâmina (y/D) acima do limite (75%) no trecho " & NumToStr(i + 1, 0) & vbCrLf
    ElseIf (yD >= 0.5) Then
        alertas = alertas & "Lâmina (y/D) maior que 50% no trecho " & NumToStr(i + 1, 0) & ". Verificar velocidade máxima." & vbCrLf
    End If
    Me.ListBoxCalc.List(trecho - 1, 1) = DblToStr(yD)
    
    ' Altera dados nos TextBoxes
    Me.TxTrecho.Value = trecho + 1
    Me.TxCTMont.Value = DblToStr(ctJus)
    Me.TxCTJus.Value = ""
    Me.TxProfMont.Value = DblToStr(profJus)
    Me.TxProfJus.Value = ""
    Me.TxComp.Value = ""
    Me.TxMaterial = mat
    Me.TxDN = NumToStr(dn, 0)
    Me.TxVazao = DblToStr(vazao)
    
End Sub

' Transforma os Doubles em Strings
Public Function DblToStr(num As Double) As String
    DblToStr = NumToStr(num, 2)
End Function

' Transforma Números em geral em Strings
Public Function NumToStr(num As Variant, precisao As Integer) As String
    Dim f
    Select Case precisao
        Case 0
            f = "###0"
        Case 1
            f = "###0.0"
        Case 2
            f = "###0.00"
        Case 3
            f = "###0.000"
        Case 4
            f = "###0.0000"
        Case 5
            f = "###0.00000"
        Case Else
            f = "###0.00"
    End Select
    
    If precisao > 0 Then
        NumToStr = Replace(format(CDbl(num), f), ".", ",")
    Else
        NumToStr = CStr(num)
    End If
    
End Function

Private Sub cmdAddLinha_Click()
    ' Variaveis
    Dim trecho As Integer, dn As Integer
    Dim ctMont As Double, ctJus As Double
    Dim profMont As Double, profJus As Double, dist As Double
    Dim mat As String
    Dim vazaoArray As Variant
    Dim vazao As Double
    Dim profTrechoAnt As Double
    alertas = ""
    
    ' Checa se a linha está completa
    ' TODO
    
    ' Popula as variáveis
    ' Número do trecho
    trecho = CInt(Me.TxTrecho.Value)
    If (trecho <= nLinhas) Then
        result = MsgBox("Trecho existente. Deseja sobrescrever?", vbYesNo, "Trecho Existente")
        ' Lida com cancelamento/confirmação
        ' TODO If result = ...
        ' ElseIf ...
        ' End If ...
    End If
    
    ' Cota de topo a montante
    ctMont = CDbl(Me.TxCTMont.Value)
    ' Cota de topo a jusante
    ctJus = CDbl(Me.TxCTJus.Value)
    ' Profundidade a montante
    profMont = valueFromString(Me.TxProfMont.Value)
    ' Profundidade a justante
    profJus = CDbl(Me.TxProfJus.Value)
    ' Distância
    dist = CDbl(Me.TxComp.Value)
    ' Material
    mat = Me.TxMaterial.Value
    ' Diâmetro
    dn = CInt(Me.TxDN.Value)
    ' Vazão
    vazaoArray = Split(Me.TxVazao.Value, "+")
    If GetLength(vazaoArray) > 0 Then
        vazao = 0
        For Each q In vazaoArray
            vazao = vazao + CDbl(q)
        Next
    End If
    If (vazao < 0) Then
        vazao = 0
    End If
        
    Call AddLinha(trecho, ctMont, ctJus, profMont, profJus, dist, mat, dn, vazao)
End Sub

' Editar a linha, ie. carrega os dados da linha selecionada na ListEdit e solicita novos dados ao usuário
Private Sub cmdEditar_Click()
    ' Variaveis
    Dim row As Integer
    Dim trecho As Integer, dn As Integer
    Dim ctMont As Double, ctJus As Double
    Dim profMont As Double, profJus As Double, dist As Double
    Dim mat As String
    Dim vazaoArray As Variant
    Dim vazao As Double
    
    With Me.ListBoxEdit
        row = .ListIndex
        If (row > -1 And .Selected(row)) Then
            trecho = CInt(.List(row, 0))
            ctMont = CDbl(.List(row, 1))
            profMont = CDbl(.List(row, 2))
            ctJus = CDbl(.List(row, 3))
            profJus = CDbl(.List(row, 4))
            dist = CDbl(.List(row, 5))
            mat = .List(row, 6)
            dn = CInt(.List(row, 7))
            vazao = CDbl(.List(row, 8))
            
            Me.TxTrecho.Value = NumToStr(trecho, 0)
            Me.TxCTMont.Value = DblToStr(ctMont)
            Me.TxCTJus.Value = DblToStr(ctJus)
            Me.TxProfMont.Value = DblToStr(profMont)
            Me.TxProfJus.Value = DblToStr(profJus)
            Me.TxComp.Value = DblToStr(dist)
            Me.TxMaterial.Value = mat
            Me.TxDN.Value = NumToStr(dn, 0)
            Me.TxVazao.Value = DblToStr(vazao)
        End If
    End With
End Sub

' Calcula a coordenada Y da cota
Public Function coordY(ct As Double) As Double
    coordY = (ct - cotaMin) * escY + dxRotulosInf
End Function

' Calcula ponto
Private Function ponto(x As Double, y As Double)
    Dim pt(0 To 2) As Double
    pt(0) = x: pt(1) = y: pt(2) = 0#
    ponto = pt
End Function

' Desenha Leader
Private Function desenhaLeader( _
    x1 As Double, y1 As Double, _
    qX As Double, qY As Double, _
    txSup As String, txInf As String) As Object
    
    ' Define os pontos
    Dim obj As Object, pt As Variant
    Dim pontos(0 To 8) As Double
    Dim x2 As Double, y2 As Double, x3 As Double, y3 As Double
    x2 = x1 + qX * projLd
    y2 = y1 + qY * projLd
    x3 = x2 + (qX / Abs(qX)) * dxLd
    y3 = y2
    pontos(0) = x1: pontos(1) = y1: pontos(2) = 0
    pontos(3) = x2: pontos(4) = y2: pontos(5) = 0
    pontos(6) = x3: pontos(7) = y3: pontos(8) = 0
        
    ' Desenha o leader
    Set obj = ThisDrawing.ModelSpace.AddLeader( _
        pontos, Nothing, acLineNoArrow)
    
    ' Texto superior
    Dim xp As Double, yp As Double
    If (qX < 0) Then
        xp = x3
    Else
        xp = x2
    End If
    yp = y2
    pt = ponto(xp, yp + offsetTextos)
    Set obj = ThisDrawing.ModelSpace.AddText(txSup, pt, htextos)
    ' Texto inferior
    Set obj = insereTexto(txInf, xp, yp - offsetTextos, _
                            AcAlignment.acAlignmentTopLeft, 0)
    
    ' Desenha os textos
    Set desenhaLeader = obj
End Function

Public Sub insereTextosTabInf(x As Double, infos As Variant)
    ' Desenha infos
    Dim ctr As Integer, y As Double
    ctr = 0
    y = -hLinhaInfo / 2
    
    ' Extensão
    While ctr < nLinhasInfo
        Call insereTexto(CStr(infos(ctr)), x, y, acAlignmentMiddleCenter, 0#)
        y = y - hLinhaInfo
        ctr = ctr + 1
    Wend

End Sub

' Desenha PV
Private Function desenhaPV(x As Double, yTopo As Double, _
                    yFundo As Double, cTopo As Double, prof As Double)
    
    ' Define variaveis
    Dim obj As Object, txObj As AcadText
    Dim mjAxis(0 To 2) As Double
    Dim cTopoStr As String, cFundoStr As String, profStr As String
    Dim x1 As Double, x2 As Double
    Dim pt
    
    profStr = DblToStr(prof)
    x1 = x - raioPV
    x2 = x + raioPV
    
    ' Desenha PV
    Set obj = ThisDrawing.ModelSpace.AddLine(ponto(x1, yTopo), ponto(x1, yFundo))
    Set obj = ThisDrawing.ModelSpace.AddLine(ponto(x2, yTopo), ponto(x2, yFundo))
    mjAxis(0) = raioPV: mjAxis(1) = 0: mjAxis(2) = 0
    Set obj = ThisDrawing.ModelSpace.AddEllipse(ponto(x, yTopo), mjAxis, escXYelPV)
    Set obj = ThisDrawing.ModelSpace.AddEllipse(ponto(x, yFundo), mjAxis, escXYelPV)
    
    ' Desenha linha central
    Set obj = ThisDrawing.ModelSpace.AddLine(ponto(x, yFundo), ponto(x, -hTabInfo))
    
    ' Desenha textos das cotas de topo e de fundo
    ' Nivel de topo
    cTopoStr = DblToStr(cTopo)
    Set txObj = insereTexto("NT " + cTopoStr, x - offsetTextos, offsetTextos, acAlignmentBottomLeft, 90)
    ' Nivel de fundo
    cFundoStr = DblToStr(cTopo - prof)
    Set txObj = insereTexto("NF " + cFundoStr, x + offsetTextos, offsetTextos, acAlignmentTopLeft, 90)
    
    ' Desenha leader de topo
    Set obj = desenhaLeader(x, yTopo, 1, 2, "PROF", DblToStr(prof))
    
    Set txObj = Nothing
    Set obj = Nothing
End Function

' Retorna se as colunas editáveis da linha estão todas preenchidas
Public Function LinhaPreenchida(row As Integer) As Boolean
    Dim col As Integer
    col = 0
    LinhaPreenchida = True
    While col < NCOLS_
        If IsEmpty(Me.ListBoxEdit.List(row, col)) Then
            LinhaPreenchida = False
            col = NCOLS
        End If
        col = col + 1
    Wend
End Function

' Retorna o cumprimento da Array
Public Function GetLength(a As Variant) As Integer
   If (IsEmpty(a)) Then
      GetLength = 0
   Else
      GetLength = UBound(a) - LBound(a) + 1
   End If
End Function

' Procura a cota máxima
Public Function cotaMaxima() As Double
    Dim col, row As Integer
    Dim cota As Double
    col = 1                 ' Coluna referente às cotas de topo
    row = 0
    cotaMaxima = 0#
    
    For row = 0 To nLinhas - 1
        cota = valueFromString(Me.ListBoxEdit.List(row, col))
        
        If (cota > cotaMaxima) Then
            cotaMaxima = cota
        End If
    Next row
End Function

' Insere o texto informando alinhamento e rotação
Public Function insereTexto(txt As String, x As Double, y As Double, _
                            alignStyle As AcAlignment, angGraus As Double) As AcadText
    ' Variaveis
    Dim txObj As AcadText
    Dim pt As Variant
    pt = ponto(x, y)
    
    ' Insere o texto
    Set txObj = ThisDrawing.ModelSpace.AddText(txt, pt, htextos)
    ' Alinha
    txObj.Alignment = alignStyle
    txObj.TextAlignmentPoint = pt
    ' Rotaciona
    Call txObj.Rotate(pt, angGraus * 3.14159 / 180)
    
    Set txObj = Nothing
End Function

' Procura a cota mínima
Public Function cotaMinima() As Double
    Dim col, row As Integer
    Dim cota As Double
    col = 3              ' Coluna referente às cotas de fundo
    cotaMinima = valueFromString(Me.ListBoxEdit.Column(1, 0))
        
    For row = 1 To nLinhas - 1
        cota = valueFromString(Me.ListBoxEdit.Column(col, row))
        If (cota < cotaMinima) Then
            cotaMinima = cota
        End If
    Next row
    
    cotaMinima = cotaMinima - offsetEixos / escY
    If (cotaMinima < 0) Then
        cotaMinima = 0
    End If
End Function

' Calcula Lâmina
' Função Auxiliar fkAux
Public Function fkAux(t As Double) As Double
    If (t = 0) Then
        fkAux = 0#
    Else
        fkAux = ((t - Sin(t)) ^ 5) / (t ^ 2)
    End If
End Function

' Vazão em litros/segundo, diam em mm, decliv em decimal (p.ex. 0,01)
Public Function lamina(vazaoLpsec As Double, diam As Integer, decliv As Double, manning As Double)
    Dim k1 As Double, k2 As Double, theta As Double
    Dim a As Double, b As Double, res As Double, err As Double
    Dim ctr As Integer
    
    ' Essa função calcula um valor k1=K a ser alcançado
    ' Calcula-se então um k2 através de ângulo central, que representa_
    ' a lâmina do líquido, por tentativa e erro até que k2 = k1.
    If ((decliv <= 0) Or (vazaoLpsec = 0#)) Then
        lamina = 0#
        Exit Function
    End If
    
    ' Cálculo de k1 = K
    ' K = fator de forma e vazão para o canal circular
    ' K = {(2^13)*[nQ/sqrt(I)]^3}/(D^8), Q em m³/s, I em mm/mm, D em metros, n = Manning
    k1 = (manning * (vazaoLpsec / 1000) / (decliv ^ (1 / 2)))
    k1 = (k1 ^ 3) * (2 ^ 13) / ((diam / 1000) ^ 8)
    
    ' Estimativa inicial para k2
    a = 0
    b = 2 * 3.14129
    ctr = 0
    theta = (a + b) / 2
    k2 = fkAux(theta)
    err = k2 - k1
    
    ' Realiza as iterações até k2 convergir p/ k1
    While ((ctr < maxTentativas) And Abs(err) > errLamina)
        If (err < 0) Then
            a = theta
        Else
            b = theta
        End If
        theta = (a + b) / 2
        k2 = fkAux(theta)
        err = k2 - k1
        ctr = ctr + 1
    Wend
    
    ' Definido o valor k2 = k1 = K, define a lâmina
    lamina = 100 * (1 - Cos(theta / 2)) / 2
End Function

' Checa se um arquivo existe
Function FileExists(FilePath As String) As Boolean
Dim TestStr As String
    TestStr = ""
    On Error Resume Next
    TestStr = Dir(FilePath)
    On Error GoTo 0
    If TestStr = "" Then
        FileExists = False
    Else
        FileExists = True
    End If
End Function

' Teste
Public Sub Teste()
End Sub
