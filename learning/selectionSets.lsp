(defun c:paintItRed()
	(setq ss (ssget "X" '((0 . "LINE,CIRCLE,TEXT,*POLYLINE"))))
	(command "chprop" ss "" "Color" "Red" "")
	(alert "Painting in red completed")
	(princ)
)

(defun c:addObject()
	(setq ss (ssadd))
	(print (sslength ss))
	(setq lines (ssget "X" '((0 . "LINE"))))
	(setq ss (ssadd (ssname lines 0) ss))
	(print "Line object was added")
	(print (sslength ss))
	(princ)
)

(defun c:delObject()
	(setq lines (ssget "X" '((0 . "LINE"))))
	(print (sslength lines))
	(setq lines (ssdel (ssname lines 0) lines))
	(print "Line object was deleted from selection set")
	(print (sslength lines))
	(princ)
)

(defun c:isMember()
	(print "Select object to the initial set: ")
	(setq ss (ssget))
	(print "Now select the object to check: ")
	(setq objName (ssname (ssget) 0))
	
	(if (ssmemb objName ss)
		(print "The object is a member of the set"); Then Expression - if obj is member of ss
		(print "The object isn't a member of the set"); Else Expression - if condition is not met
	)
	(princ)
)

(defun c:getRadius()
	(setq ss (ssget "X" '((0 . "CIRCLE"))))
	(setq radius1 (getpropertyvalue (ssname ss 0) "radius"))
	(setq radius2 (getpropertyvalue (ssname ss 1) "radius"))
	(prompt (strcat "\nRadius of the 1st circle: " (rtos radius1)))
	(prompt (strcat "\nRadius of the 2nd circle: " (rtos radius2)))
	(princ)
)

(defun c:getNumber()
	(setq lines (ssget "X" '((0 . "LINE"))))
	(alert (strcat "There are " (rtos (sslength lines)) " lines in the drawing"))
	(setq plines (ssget "X" '((0 . "LWPOLYLINE")(8 . "Road"))))
	(alert (strcat "There are " (rtos (sslength plines)) " roads in the drawing"))
	(setq texts (ssget "X" '((0 . "*TEXT")(7 . "ITALIC"))))
	(alert (strcat "There are " (rtos (sslength texts)) " italic texts in the drawing"))
	(princ)
)
